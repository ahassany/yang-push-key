module ietf-interfaces {
  namespace "urn:ietf:params:xml:ns:yang:ietf-interfaces";
  prefix if;
  container interfaces {
    list interface {
      key "name";
      leaf name        { type string; }
      leaf oper-status { type enumeration { enum up; enum down; } }
      leaf mtu         { type uint16; }
      leaf description { type string; }
    }
  }
}
